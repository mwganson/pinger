## Pinger macro
## By: TheMarkster
## 2020.07.22
## Aids in pinging users on the forum
## Select the user from the list and paste clipboard contents into the forum

import time
from PySide import QtGui,QtCore
from PySide2 import QtWebEngineWidgets as Web
limitToTopNUsers = 10000 #change to 100 for example to use only top 100 users (by number of posts)
dict1 = {'chrisb': '5646', 'NormandC': '202', 'wmayer': '69', 'yorik': '68', 'bernd': '2069', 'jmaustpc': '611', 'triplus': '782', 'DeepSOIC': '3888', 'Kunda1': '12229', 'freecad-heini-1': '2598', 'bejant': '1940', 'sgrogan': '4252', 'microelly2': '2364', 'vocx': '21943', 'openBrain': '22265', 'wandererfan': '1375', 'quick61': '2030', 'abdullah': '3232', 'jriegel': '67', 'looo': '2349', 'mario52': '1058', 'PrzemoF': '3666', 'ickby': '686', 'meme2704': '14145', 'easyw-fc': '6387', 'shoogen': '765', 'renatorivo': '918', 'paullee': '8738', 'GlouGlou': '5772', 'kisolre': '22435', 'r-frank': '1529', 'kkremitzki': '7997', 'Jee-Bee': '6234', 'papyblaise': '25808', 'Anonymous': '1', 'ulrich1a': '1928', 'herbk': '4353', 'sliptonic': '708', 'Joel_graff': '14673', 'thschrader': '15166', 'rockn': '681', 'TheMarkster': '19292', 'realthunder': '12167', 'uwestoehr': '23505', 'tanderson69': '208', 'saso': '3305', 'mlampert': '10163', 'freedman': '19098', 'Roy_043': '22936', 'carlopav': '23005', 'Willem': '9760', 'Chris_G': '2561', 'keithsloan52': '930', 'GeneFC': '8180', 'roerich_64': '6075', 'HarryGeier': '15774', 'UR_': '12184', 'hammax': '12483', 'HoWil': '6222', 'freman': '22524', 'HarryvL': '18062', 'drmacro': '2867', 'bitacovir': '3136', 'Forthman': '19652', 'peterl94': '1819', 'cox': '4523', 'kbwbe': '19380', 'Zolko': '22794', 'reox': '9769', 'pablogil': '4517', 'HakanSeven12': '23711', 'ArminF': '11953', 'RatonLaveur': '24547', 'jeno': '3508', 'thomas-neemann': '29293', 'flachyjoe': '984', 'regis': '6401', 'Syres': '21041', 'ian.rees': '3449', 'pperisin': '356', 'ppemawm': '1807', 'mrlukeparry': '607', 'logari81': '270', 'fc_tofu': '29038', 'ezzieyguywuf': '6058', 'emills2': '5929', 'vejmarie': '7506', 'Dirk.B': '23630', 'eivindkvedalen': '1546', 'damian': '6134', 'jrheinlaender': '997', 'Jimidi': '15956', '-alex-': '23825', 'dubstar-04': '1642', 'Gift': '6611', 'Joyas': '3582', 'drei': '3278', 'cappy0815': '4130', 'Bance': '5418', 'Russ4262': '20523', 'r.tec': '4264', 'agryson': '11337', 'dcapeletti': '3651', 'manuelkrause': '20592', 'Mar': '14191', 'JoshM': '16808', 'teobo': '2833', 'jpg87': '13810', 'schupin': '18259', 'danielfalck': '689', 'makkemal': '5932', 'Fran': '16427', 'onekk': '5245', 'bill': '5185', 'oliveroxtoby': '11950', 'leoheck': '19003', 'fandaL': '3658', 'blacey': '7328', 'shaise': '6188', 'johnwang': '23504', 'fosselius': '8591', 'fran6t': '3600', 'nemesis': '2986', 'herrdeh': '3918', 'holdi': '11560', 'piffpoof': '4556', 'furti': '17491', 'adrianinsaval': '19302', 'f3nix': '6125', 'jreinhardt': '2072', 'chakkree': '6331', 'galou_breizh': '334', 'bavariaSHAPE': '3425', 'FaDa3D': '16107', 'jaisejames': '10269', 'apeltauer': '16146', 'plgarcia': '6249', 'fcaduser': '2823', 'jp-willm': '7776', 'Pauvres_honteux': '2803', 'clintonsam75': '3470', 'Claud': '29138', 'amrit3701': '9146', 'OldDraftsman': '16332', 'ebrahi': '21433', 'Sudhanshu': '21878', 'usbhub': '24632', 'efyx': '4074', 'jbe': '2330', 'JMG': '2538', 'kwahoo': '2441', 'lemonbug': '4228', 'Repman': '3536', 'koluna': '21576', 'polymer': '3974', 'Moult': '23100', 'joha2': '10551', 'david69': '2566', 'Roland': '6638', 'Konstantin': '3649', 'Renat': '3315', 'hobbes1069': '725', 'blonblon': '10279', 'oldmachine': '15343', 'wega': '2347', 'user1234': '9411', 'salp': '2409', 'Drederwisch': '11726', 'arturromarr': '15598', 'bgoodr': '3447', 'jruiz': '4299', 'arcol': '2320', 'garya': '22407', 'CharlieMAC': '3179', 'blue0cean': '23920', 'Marco_T': '7564', 'kaktus': '26846', 'lainegates': '1295', 'davecoventry': '2481', 'FC-Architecter': '19079', 'Sura': '21412', 'chrisf': '2578', 'ceremcem': '18069', 'ediloren': '1783', 'dxp.dev': '22713', 'jean.thil': '6498', 'qingfeng.xia': '6825', 'pl7i92LCNC': '24265', 'OficineRobotica': '23938', 'kwahooo': '254', 'j-dowsett': '652', 'memfis': '11177', 'nahshon': '1973', 'yoshimitsuspeed': '1337', 'cram': '11546', 'HartmutG': '10744', 'gdo35': '858', 'ProBowlUk': '4171', 'freecadjam': '20736', 'HBC0': '6833', 'catman': '23210', 'paul18': '3622', 'rentlau_64': '4246', 'AR795': '20058', 'heilo': '12525', 'hardeeprai': '255', 'Turro75': '9800', 'joel': '12631', 'Fat-Zer': '4325', 'Sam': '8192', 'Giuli': '9935', 'kanagan': '5980', 'jnxd': '5734', 'S.N.A.L': '3080', 'Renato': '5905', 'papy': '21427', 'Markymark': '28078', 'm42kus': '3911', 'M4x': '13711', 'freecc': '18704', 'Brutha': '5971', 'cblt2l': '251', 'un1corn': '7434', 'Leatherman': '12789', 'TopDown': '20410', 'gsandy': '23521', 'psicofil': '789', 'project4': '1944', 'crobar': '3893', 'a3bksll47': '19044', 'TomB19': '25136', 'dimitar': '25801', 'rynn': '20919', 'wsteffe': '3846', 'industromatic': '2997', 'MaurinoWeb': '15573', 'nyholku': '12058', 'wvmarle': '4214', 'derschutzhund': '3592', 'sanguinariojoe': '574', 'MSOlsen65': '29727', 'crashfridh': '1483', 'Anderl': '17746', '1D_Inc': '23696', 'ektus': '1283', 'Eric': '25272', 'ikua': '14240', 'hhassey': '6158', 'japie': '3493', 'zbigg': '17804', 'clytle374': '2207', 'C_h_o_p_i_n': '25037', 'Mongrel_Shark': '10595', 'FemUser': '16291', 'Spindoctor': '6848', 'foxint': '7589', 'dan-miel': '21478', 'oddtopus': '10205', 'IzzY': '14602', 'xibinke': '5703', 'aapo': '22095', 'jakob': '3595', 'jonasthomas': '873', 'schnebeck': '15579', 'ajoeiam': '24132', 'lot': '25410', 'JiPe38': '28975', 'scrungy_doolittle': '20416', 'kcleung': '512', 'eason': '5803', 'KAP': '28935', 'Luixx': '18322', 'iplayfast': '27301', 'prrvchr': '4119', 'brjhaverkamp': '6838', 'roivai': '12794', 'bbear123': '2465', 'cnirbhay': '9824', 'mnesarco': '30314', 'alex::freecad': '3892', 'more11': '4079', 'kreso-t': '20975', 'Hannu': '6761', 'heideachim': '18226', 'Galahad': '20671', 'Wsk8': '22665', 'aguseguedre': '535', 'frecd': '5116', 'Do': '11781', 'hds': '13102', 'Jos': '31258', 'rjpeek': '7415', 'babaroga': '9780', 'etrombly': '28581', 'Norus': '6964', 'Koemi': '17917', 'EkaitzEsteban': '21473', 'rebeltaz': '24648', 'NateM': '2390', 'django013': '5218', 'jmplonka': '11876', 'm0n5t3r': '12818', 'sibelius': '29023', 'lhagan': '108', 'tom': '5727', 'Daniel84': '13510', 'Andr': '7655', 'm.cavallerin': '20120', 'bzb.dev001': '25224', 'neondata': '1573', 'DrBwts': '4281', 'albertdela': '16540', 'Gauthier': '3532', 'balazs': '4211', 'atzensepp': '5514', 'spikey': '7624', 'Cyril': '16289', 'OakLD': '18151', 'waebbl': '21119', 'oldestfox': '1910', 'Xav-83': '3750', 'jmh': '4317', 'Linden': '6627', 'Lauri': '13429', 'vanuan': '22024', 'andre': '2370', 'j9lemmon': '2018', 'Crossleyuk': '20393', 'iogui': '24401', 'godblessfq': '6436', 'mack5': '15924', 'falviani': '25270', 'mandeep7': '8229', 'Tilli': '18331', 'onesz': '729', 'Maavhamt': '6189', 'capucin': '16725', 'ckl6767': '24834', 'Opus': '17261', 'ccccrnr': '698', 'Serchu': '5411', 'foadsf': '5587', 'NC3D': '10606', 'luggw1': '13046', 'dave_w': '30076', 'jobermayr': '769', 'murdic': '2856', 'tanj': '16319', 'MrRossi': '11492', 'agima2': '12024', 'Enyalios': '13094', 'abasel': '21318', 'brst': '24863', 'jdurston': '697', 'zohozer': '3684', 'christi': '22009', 'Tamirov.ru': '23726', 'petit_chat_noir': '27642', 'dino': '4044', 'Quaoar': '15966', 'svenair': '4549', 'A_3': '7639', 'mdhill': '14574', 'otoien': '16164', 'dulouie': '16780', 'abcb': '23151', 'fcaponi78': '1007', 'jcc242': '1017', 's-light': '5425', 'Fantaspic': '11388', 'Routerworks': '19363', 'magwas': '615', 'detlet': '676', 'josheeg': '2362', 'IanP': '7957', 'Matael': '7975', 'cadgiru': '10838', 'Thoma': '13437', 'serrepattes': '15169', 'BassMati': '21785', 'carlod': '684', 'tilas': '717', 'helo10': '917', 'tomkcook': '9516', 'wafi': '10594', 'miniellipse': '19613', 'ldboehm': '20298', 'PunyTune': '23110', 'Bayesian': '26807', 'salatwork': '1044', 'hinckel': '4480', 'dbecad': '19043', 'mfasano': '19405', 'mdinger': '2928', 'mrdic': '14954', 'JOE_FU': '23194', 'micksulley': '19859', 'M3RS2': '20695', 'mk2': '4637', 'seppelw': '18203', 'DDM': '23687', 'Cobraschock': '25890', 'dchigrin': '397', 'JLB85FR': '7593', 'Magnum56': '19253', 'nic': '24865', 'jacknotreally': '181', 'jmwright': '3465', 'Rei': '8970', 'lambda': '13391', 'David_D': '20509', 'flowwie': '23494', 'Gustav180': '6328', 'doubters': '8165', 'DAP': '9480', 'gpmari1': '11120', 'DaveGlx': '4332', 'sodelo': '12583', 'sweepy': '13775', 'maker': '19242', 'Piero69': '26052', 'hrhassan': '31926', 'angow': '779', 'roegel': '3782', 'hamish': '4408', '_taras_': '6417', 'kishore': '9122', 'IMback!': '26160', 'shinwu': '3908', 'Pascal': '13929', 'froussel': '15460', 'pPodest': '23873', 'tonyaimer': '27612', 'fmluizao': '28364', 'obijuan': '3679', 'lutz_dd': '3703', 'TT-RS': '4271', 'EdgarRobles': '6517', 'FATH': '15765', 'Ukacor': '24411', 'geolux': '25205', 'archang': '3878', 'Tomas': '7799', 'Boneshaker': '7905', 'hatari': '9540', 'rus': '13334', 'disenator': '4213', 'PAT64': '8949', 'prandall': '13151', 'leonardshelby': '18760', 'Chri1': '21908', 'Aleks': '30029', 'demackison': '4500', 'AdamTimm': '7607', 'fester2251': '780', 'cahlfors': '856', 'serviteur': '4419', 'KgoaOT': '9484', 'kemeniru': '439', 'Ca': '4520', 'whirlybomber': '2011', 'fmd14': '6662', 'darrenmsmith': '25371', 'jbet': '1126', 'maggus': '2743', 'ShurikMur': '6707', 'Moebius': '7796', 'mmiscool': '11849', 'Johnquicker': '21100', 'SvenGoord': '23886', 'DeeJayOne': '27274', 'sandman': '2966', 'amka': '6715', 'Badapower': '8291', 'hokieengr': '12126', 'simonvanderveldt': '13769', 'ggcode': '15955', 'mindflow': '22351', 'carsco': '26076', 'twohot': '529', 'Sawfish': '3853', 'grandcross': '6949', 'liutas4x4': '9464', 'shivaksingh': '14160', 'retnev': '17745', 'fjullien': '18209', 'gbroques': '29296', 'midgetfc': '87', 'tobaggo17': '5238', 'adamLange': '6083', 'freecadlzh': '30003', 'CkwA': '3982', 'icare': '7109', 'Berci': '7836', 'silopolis': '10730', 'Blumfeld': '17520', 'Henri33': '17862', 'SupDoc': '27958', 'momentumv5': '742', 'ralvejd': '1613', 'poserge': '5777', 'Tato3d': '24848', 'manday': '561', 'ryback08': '832', 'ubit': '4910', 'Eneen': '6581', 'Eagle': '6597', 'jbi': '8611', 'Poppa': '19578', 'Berser': '20335', 'Tripplex': '20600', 'czinehuba': '21877', 'JulianTodd': '21998', 'Danilo0702': '23597', 'cline': '187', 'sket': '3276', 'mafer78': '6854', 'Halfa': '7541', 'eexpss': '12046', 'gntech': '15224', 'Dex': '16697', 'tommeyers': '19016', 'danreb': '19019', 'flim': '19800', 'jmueti': '25770', 'ole84': '322', 'vu2011': '701', 'misterkeeks': '1352', 'diep': '2502', 'wieszak17': '2621', 'dammerel': '3759', 'LotusChang': '3873', 'Geraldhemel2': '3998', 'duk': '6049', 'alberich': '16220', 'mad_max': '20513', 'zacl': '26705', 'jumbo125': '27897', 'luuv': '2084', 'DomiChi': '2975', 'lalberts': '7771', 'Rod': '7918', 'cad-gast2': '8704', 'Christoph': '9381', 'fjaffre': '26169', 'albertof': '235', 'robinh': '3209', 'JAndersM': '7413', 'bypbop': '7808', 'jcf': '11165', 'the_document': '18028', 'felixlee868': '26041', 'brusk': '5465', 'Lotharyx': '7906', 'h.tsubota': '8207', 'Condor-2-4-2': '16547', 'xeres': '20521', 'dekoning': '4462', 'kryptokommunist': '30335', 'psi13art': '344', 'peepsalot': '735', 'laurent_parti': '2861', 'Georg99': '4382', 'tryer': '6702', 'cflin': '15048', 'business_kid': '15574', 'Celica_Supra': '22176', 'lelectronlibre': '28031', 'mpetrasinovic': '29784', 'Gregor': '30570', 'mpyusko': '516', 'djreichel': '908', 'Sanguinario_Joe': '2564', 'Robavh': '3838', 'yves78': '4521', 'JeffWitz': '5714', '18turbo': '6731', '71GA': '14043', 'federico.carminati': '15114', 'roo': '16003', 'joancabeza': '19271', 'gflorent': '21049', 'topcyde': '2880', 'claus1982': '2971', 'antoniovazquezblanco': '3050', 'julianfoad': '5989', 'überfuzz': '7792', 'flopsy': '7942', 'tantle1961': '12016', 'soaring': '12129', 'geobruce': '19970', 'ian9toes': '20230', 'JiriVALASEK': '24857', 'thalesavionics': '959', 'marktaff': '4033', 'FreeRadical': '4396', 'terok': '17808', 'lota': '17987', 'toralf': '25178', 'raback': '31306', 'c-m-burns2': '1405', 'simsiem': '7742', 'lesept': '19326', 'volodia': '19505', 'Chaospilot': '22486', 'benjaminwharton': '24013', 'ifohancroft': '25644', 'Hartwig': '26727', 'nvivier': '172', 'electronlibre': '778', 'Mika38': '13015', 'Dekonstruierer': '15592', 'RickDeckard': '18194', 'marmni': '2444', 'mangtronix': '3132', 'SBW': '4651', 'Doug': '13425', 'ceving': '16604', 'anatolli': '19728', 'hooshsim': '22205', 'dpettegrew': '23764', 'JoshuaCall': '28753', 'l-m88': '207', 'splineman': '283', 'linuxer': '4258', 'Yinameah': '5412', 'jidoeuf': '5539', 'andrigtmiller': '7704', 'kryscosne': '7982', 'Alex68': '9367', 'josegegas': '13017', 'tcs_ulrich': '16343', 'otto9F9otto': '19334', 'ljb': '21357', 'tööö': '25907', 'q_9': '27607', 'gege81100': '28175', 'edi': '29214', 'TedM': '30824', 'iari': '2396', 'benoit': '2936', 'AvgJoe': '4099', 'EskiBrew': '5906', 'berka': '6645', 'Laurent239': '6845', 'elsordo': '7721', 'idfx': '7868', 'Olav': '11423', 'probono': '12070',

#add new users and userids here
#some examples:
'Enyalios': '13094',
'agima2': '12024'

}

def getClipText():
    clip = QtGui.QClipboard()
    return clip.text(QtGui.QClipboard.Clipboard)

def setClipText(txt):
    clip = QtGui.QClipboard()
    clip.setText(txt)

def parseHtml(txt):
    """parse html copied from list of users view source
returns dictionary of usernames and user ids"""
    lines = txt.split()
    dictionary = {}
    userNext = True
    idNext = False
    currentUser = ""
    currentId = ""
    for line in lines:
        if "class=\"username" in line:
            currentUser = line[line.find('>')+1:line.find('<')]
            currentUser = currentUser.replace(' ','_')
        elif "author_id=" in line:
            currentId = line[line.find("id=")+3:line.find("&sr=posts")]
            dictionary[currentUser] = currentId
    return dictionary

        


class CallbackFactory():
    def __init__(self, param):
        self.param = param
    def doIt(self):

        script = """
var tbl = document.getElementsByClassName("table1")[0];
var txt = tbl.innerHTML;
var myHTML = "<html><body><form><textarea id='ta' rows='5' cols='60'>"+txt+"</textarea>\\n";
myHTML += "<input type='button' id='btn' onclick='copy()' value='clickme'></input>\\n";
myHTML += "<script>\\n";
myHTML += "function copy(){\\n";
myHTML += "    var ta = document.getElementById('ta');\\n";
myHTML += "    ta.select();\\n";
myHTML += "    document.execCommand('copy');\\n";
myHTML += "    var btn = document.getElementById('btn');\\n";
myHTML += "    btn.style.visibility='hidden';\\n";
myHTML += "};\\n";

myHTML += "</script><body></html>"
document.write(myHTML);

"""

        #webviews[-1].page().runJavaScript(script)
        self.param.runJavaScript(script)
#        [Msg(txt+'\n') for txt in dir(self.param)]
        Msg(self.param.selectedText())

if getClipText() == '':
    url_to_scrape = 'https://forum.freecadweb.org/memberlist.php?g=2&sk=d&sd=d&mode=group&start='
    folder = 'c/users/mwganson/Documents/projects/pinger/'
    webviews = []
#webview.load(url_to_scrape+'0')
    jj=0
    callbacks = {}
    for ii in range(2500,2024,-25):

        webviews.append(Web.QWebEngineView())
        webviews[-1].load(url_to_scrape+str(ii))
        callbacks[str(jj)] = CallbackFactory(webviews[-1].page())
        webviews[-1].loadFinished.connect(callbacks[str(jj)].doIt)
        webviews[-1].setWindowTitle(str(ii))
        webviews[-1].show()
        jj += 1


    #items = ["select user to ping","copy FreeCAD about info"]
    #username,ok = QtGui.QInputDialog.getItem(QtGui.QMainWindow(),"Select user", "Select user:",items,0,0)

    
#def callback(param):
#
#    #webview.page().save(folder+'page'+str(ii).zfill(3)+'.html')
#    #Msg('saved...\n')
#script = """
#var tbl = document.getElementsByClassName("table1")[0];
#var txt = tbl.innerHTML;
#var myHTML = "<textarea id='ta' rows='5' cols='25'>"+txt+"</textarea>\\n<script>\\n";
#myHTML += "document.getElementById('ta').select();\\n";
#myHTML += "</script>"
#document.write(myHTML);
#"""

        #webviews[-1].page().runJavaScript(script)
        #param.runJavaScript(script)

#following code used to generate original dictionary
#open the member list on the freecad website
#sort by number of posts
#right click, view source
#copy all html to the clipboard, run macro
#in report view will be 25 username / userid keys
#uncomment the next 3 lines and run
else:
    Msg('parsing...')
    url = getClipText()
    userDict = parseHtml(url)
    msg = 'dict1 = '+str(userDict).replace('}',',')
    setClipText(msg)
    Msg(str(len(userDict.keys())))
